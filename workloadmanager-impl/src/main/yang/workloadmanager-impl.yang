module workloadmanager-impl {
    yang-version 1;
    namespace "urn:opendaylight:params:xml:ns:yang:workloadmanager:impl";
    prefix "workloadmanager-impl";

    import config { prefix config; revision-date 2013-04-05; }
    import opendaylight-md-sal-binding { prefix md-sal-binding; revision-date 2013-10-28;}

    description
        "Service definition for armoury project - workloadmanager";

    revision "2014-12-10" {
        description
            "Initial revision";
    }

    identity workloadmanager {
        base config:module-type;
        config:java-name-prefix WorkloadManager;
    }

    augment "/config:modules/config:module/config:configuration" {
        case workloadmanager {
            when "/config:modules/config:module/config:type = 'workloadmanager'";
            container broker {
                uses config:service-ref {
                    refine type {
                        mandatory true;
                        config:required-identity md-sal-binding:binding-broker-osgi-registry;
                    }
                }
            }
        }
    }
}
