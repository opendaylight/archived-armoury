module workloadmanager {
    yang-version 1;
    namespace "urn:opendaylight:params:xml:ns:yang:workloadmanager";
    prefix "workloadmanager";

    import catalog { prefix catalog; revision-date 2015-09-07; }

    contact "Ariel Noy <ariel.noy@hpe.com>";

    revision "2015-09-18" {
        description "Initial revision of workloadmanager armoury model";
    }


    typedef vnfstatus {
        type enumeration {
             enum start {
                 value "0";
             }
             enum stop {
                 value "1";
             }
             enum suspend {
                 value "2";
             }
             enum running {
                 value "3";
             }
        }
    }

    grouping VNFStatus {
        leaf status {
            type vnfstatus;
        }
    }

    grouping VNFInstance {
        description "VNF Instance";
        leaf name {
            description "Name of the VNF Instance";
            type string;
        }
        container type {
	    description "Type of the VNF";
            uses catalog:network-function;
        }
        leaf status {
            description "Status of the VNF";
            type vnfstatus;
        }

    }

    rpc status {
        input {
            uses VNFInstance;
        }
        output {
            uses VNFStatus;
        }
    }

    rpc create {
        input {
            uses catalog:network-function;
        }
        output {
            uses VNFInstance;
        }
    }

    rpc delete {
        input {
            uses VNFInstance;
        }
    }

    rpc start {
        input {
            uses VNFInstance;
        }
    }

    rpc stop {
        input {
            uses VNFInstance;
        }
    }

    rpc suspend {
        input {
            uses VNFInstance;
        }
    }

    rpc resume {
        input {
            uses VNFInstance;
        }
    }

}
